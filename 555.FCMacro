import FreeCAD as App
import Draft 
import numpy as np
import pandas as pd
from numpy import genfromtxt
#doc = App.newDocument()

def make_grid (grid_direction, dx,dy, initial_point_x, initial_point_y, piles_offset_dx, piles_offset_dy ):
	if grid_direction=="north-west":
		direction_coeff_x=-1
		direction_coeff_y=1
	grid_direction="north-east"
	if grid_direction=="north-east":
		direction_coeff_x=1
		direction_coeff_y=1
	grid_direction="south-west"
	if grid_direction=="south-west":
		direction_coeff_x=1
		direction_coeff_y=-1
	grid_direction="south-east"
	if grid_direction=="south-east":
		direction_coeff_x=-1
		direction_coeff_y=-1
	x=np.linspace(initial_point_x,(initial_point_x+dx*n_piles_x)*direction_coeff_x,dx)
	y=np.linspace(initial_point_y,(initial_point_y+dy*n_piles_y)*direction_coeff_y,dy)
	xv,yv=np.meshgrid(x,y)
	array=np.zeros((dx*dy,2)) # здесь слабое место. если массив не будет квадратным
	k=0
	
	for i in range(xv.shape[0]):
		X=xv[1,i]
		for j in range(xv.shape[0]):   # здесь слабое место. если массив не будет квадратным
			Y=yv[j,1]
			array[k,0]=X
			array[k,1]=Y
			k=k+1
	
#grid purple
	pl=FreeCAD.Placement()
	A=np.zeros((dx-1,4))
	for i in range(dx):
		doc = App.activeDocument()	
		Line_grid_name='Line7'+str(i)
		Line_grid_name = doc.addObject("Part::Line",Line_grid_name)
		Line_grid_name.Y1 =x[dx-1-i-0]+10
		Line_grid_name.X1 =y[0]+100
		Line_grid_name.Y2 =x[dx-i-1-0-dy-0]+10
		Line_grid_name.X2 =y[dy-1-0]-60
		Line_grid_name2=App.activeDocument().copyObject(Line_grid_name)
		Draft.move([Line_grid_name2],FreeCAD.Vector(0,5,0))
		Draft.rotate([Line_grid_name2],90,pl.Base)	
	return (array)
#квадрат свая
def rec1(x, y, index):
	rec_name = 'Rectangle'+str(index)
	pl = FreeCAD.Placement()
	pl.Base = FreeCAD.Vector(x+5, y+5)
	rec_obj = Draft.make_rectangle(10, 10, placement=pl, face=False, support=None)
	FreeCAD.ActiveDocument.recompute()
	return(rec_obj)

	for i in range(5):
		rectangle = rec1(0, 0, i)
		rectangles.append(rectangle)
#крест
def arr_cross(x, y, index):
	Line_cross='Line8'+str(index)
	Line_cross2='Line9'+str(index)
	doc = App.activeDocument()
	Line_cross = doc.addObject("Part::Line",Line_cross)
	Line_cross.X1 =56+x-51
	Line_cross.Y1 =55+y-50
	Line_cross.X2 =66+x-51
	Line_cross.Y2 =65+y-50

	Line_cross2 = doc.addObject("Part::Line",Line_cross2)
	Line_cross2.X1 =56+x-51
	Line_cross2.Y1 = 65+y-50
	Line_cross2.X2 = 66+x-51
	Line_cross2.Y2 =  55+y-50
	
	FreeCAD.ActiveDocument.recompute()
	return(Line_cross,Line_cross2)
	line_array = [Line8, Line9]
	for i in range(5):
		Line8, Line9 = line_cross(0, 0, i)
		line_array.append((Line8, Line9))
	
	FreeCAD.ActiveDocument.recompute()
def txt_line_size(dx, dy, index):
	t3_name='t3'+str(index)
	t4_name='t4'+str(index)
	t3 = "5"
	p3 = App.Vector(-50+dx+75, 150)
	
	t4 = ["5"]
	p4 = App.Vector(-125,85+dy-65)
	
	text3 = Draft.make_text(t3, p3)
	text4 = Draft.make_text(t4, p4)
	text3.ViewObject.FontSize = 0.005
	text4.ViewObject.FontSize = 0.005
	FreeCAD.ActiveDocument.recompute()
	return(t3, t4)
	txt_array = [t3, t4]
	for i in range(4):
		t3, t4 = text(0, 0, i)
		txt_array.append((t3, t4))
	FreeCAD.ActiveDocument.recompute()


	

def arrow_func(x,y,dx,dy,index):
	cirlce_name='Circle'+str(index)
	Line1_name='Line1'+str(index)
	Line2_name='Line2'+str(index)
	Line3_name='Line3'+str(index)
	group_name='Group'+str(index)
	group_name2='Group2'+str(index)
	group_name3='Group3'+str(index)
	Line4_name='Line4'+str(index)
	Line5_name='Line5'+str(index)
	Line6_name='Line6'+str(index)
	t_name='t1'+str(index)
	t2_name='t2'+str(index)
	p_vector='p1'+str(index)
	p2_vector='p2'+str(index)

	#Свая1
	pl=FreeCAD.Placement()
	pl.Base=FreeCAD.Vector(10,10, 0)
	cirlce_name = Draft.make_circle(radius=5, placement=pl, face=False, support=None)
	cirlce_name.Label='Circle'+str(index)

	#стрелка1
	doc = App.activeDocument()
	Line1_name = doc.addObject("Part::Line",Line1_name)
	Line1_name.X1 = 10
	Line1_name.Y1 = 10
	Line1_name.X2 = 18
	Line1_name.Y2 = 10
       
	doc = App.activeDocument()
	Line2_name = doc.addObject("Part::Line",Line2_name)
	Line2_name.X1 = 18
	Line2_name.Y1 = 10
	Line2_name.X2 = 16.2
	Line2_name.Y2 = 10.5
	        
	doc = App.activeDocument()
	Line3_name = doc.addObject("Part::Line",Line3_name)
	Line3_name.X1 = 18
	Line3_name.Y1 = 10
	Line3_name.X2 = 16.2
	Line3_name.Y2 = 9.5
	
	Line4_name=App.activeDocument().copyObject(Line1_name)
	Line5_name=App.activeDocument().copyObject(Line2_name)
	Line6_name=App.activeDocument().copyObject(Line3_name)

	p1 = App.Vector(9, 10)
	t_name = Draft.make_text(str(abs(dy)), p1)
	t_name.ViewObject.FontSize = 0.0035
		
	p2 = App.Vector(10, 9)
	t2_name = Draft.make_text(str(abs(dx)), p2)
	t2_name.ViewObject.FontSize = 0.0035
	

	group_name = App.ActiveDocument.addObject("App::DocumentObjectGroup", group_name)
	group_name.addObjects([cirlce_name,Line1_name, Line2_name, Line3_name,Line4_name,Line5_name,Line6_name,t_name,t2_name])
	group_name2 = App.ActiveDocument.addObject("App::DocumentObjectGroup", group_name2)
	group_name2.addObjects([Line4_name, Line5_name, Line6_name,t2_name])
	group_name3 = App.ActiveDocument.addObject("App::DocumentObjectGroup", group_name3)
	group_name3.addObjects([cirlce_name,group_name,group_name2])
	
	
	if dy<0:
		Draft.rotate([Line1_name,Line2_name,Line3_name],0,pl.Base)
		Draft.move([t_name],FreeCAD.Vector(10,0,0))
		
	if dy>0:
		Draft.rotate([Line1_name,Line2_name,Line3_name],180,pl.Base)
		Draft.move([t_name],FreeCAD.Vector(-12,0,0))
		
	if dy==0:
		Draft.rotate([Line1_name,Line2_name,Line3_name],180,pl.Base)
		Draft.move([t_name],FreeCAD.Vector(-12,0,0))
	if dx<0: 
		Draft.rotate([Line4_name,Line5_name,Line6_name],90,pl.Base)
		Draft.move([t2_name],FreeCAD.Vector(0,10,0))
	if dx>0: 
		Draft.rotate([Line4_name,Line5_name,Line6_name],270,pl.Base)
		Draft.move([t2_name],FreeCAD.Vector(0,-10,0))
	if dx==0:
		Draft.rotate([Line1_name,Line2_name,Line3_name],90,pl.Base)
		Draft.move([t2_name],FreeCAD.Vector(0,-10,0))
	
	Draft.move(group_name.OutList,FreeCAD.Vector(x,y,0),copy=False)
	Draft.move(group_name2.OutList,FreeCAD.Vector(x,y,0),copy=False)
	Draft.move(group_name3.OutList,FreeCAD.Vector(x,y,0),copy=False)
	
	FreeCAD.ActiveDocument.recompute()

#данные сетки(масштаб)
initial_point_x=51
initial_point_y=51
dx=5
dy=5
n_piles_x=5
n_piles_y=5
grid_direction="north-west"
piles_offset_dx=50
piles_offset_dy=50
# делаем сетку по ДС
grid=make_grid (grid_direction, dx,dy, initial_point_x, initial_point_y, piles_offset_dx, piles_offset_dy)
deviations=np.zeros((grid.shape[0],2))
#импортируем файл с "измерениями"
np.genfromtxt('C:/Users/Julian/Desktop/plusrandom.csv', delimiter=';', dtype=None)
f = open("C:/Users/Julian/Desktop/plusrandom.csv")
a=np.array(f)
arr = np.genfromtxt("C:/Users/Julian/Desktop/plusrandom.csv", delimiter=";")
#вычисляем отклонения
for i in range(grid.shape[0]):
	dev_x=arr[:,0]-grid[i,0]
	dev_y=arr[:,1]-grid[i,1]
	dev_xy=dev_x**2+dev_y**2
	index_min=np.argmin(dev_xy)
	deviations[i,0]=dev_x[index_min]
	deviations[i,1]=dev_y[index_min]
deviations=np.round(deviations,0)
for i in range(grid.shape[0]):
	arrow_func(grid[i,0],grid[i,1],deviations[i,0],deviations[i,1],i)
	rec1(grid[i,0],grid[i,1],i)
	arr_cross(grid[i,0],grid[i,1],i)
	txt_line_size(grid[i,0],grid[i,1],i)
